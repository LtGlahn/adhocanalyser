FME workspace trafikkmengdeoverlapp.fmw

Parameters:
- SourceDataset_XLSXR = $(FME_MF_DIR)Overlapp Trafikkmengde.xlsx   # Source Microsoft Excel File(s)
- DestDataset_XLSXW = $(FME_MF_DIR)trafikkmengdeoverlapp_beriket.xlsx   # Destination Microsoft Excel File

Readers:
- XLSXR_1: XLSXR from $(SourceDataset_XLSXR)

Writers:
- XLSXW_1: XLSXW to $(DestDataset_XLSXW)

Ark1 (reader XLSXR_1)
    attributes: NVDB-ID number(10,0), Versjon number(3,0), Start date, Slutt date, NVDB-ID00 number(10,0), Versjon00 number(3,0), Start00 date, Slutt00 date, Node number(8,0), Start01 number(11,8), Slutt01 number(11,8), År, gjelder for number(5,0), Veg char(8), Strekning char(11), Sekvens number(7,0), Del char(4), Q char(71), R char(71), S char(68), T char(68)
    -> AttributeManager
AttributeManager
    ATTR_TABLE:
      RENAME_SET_VALUE NVDB-ID > Mengde 1 NVDB-ID
      RENAME_SET_VALUE Versjon > Mengde 1 Versjon
      RENAME_SET_VALUE Start > Mengde 1 startdato
      RENAME_SET_VALUE Slutt > Mengde 1 sluttdato
      RENAME_SET_VALUE NVDB-ID00 > Mengde 2 NVDB-ID
      RENAME_SET_VALUE Versjon00 > Mengde 2 versjon
      RENAME_SET_VALUE Start00 > Mengde 2 startdato
      RENAME_SET_VALUE Slutt00 > Mengde 2 sluttdato
      RENAME_SET_VALUE Node > VeglenkesekvensId
      RENAME_SET_VALUE Start01 > startposisjon
      RENAME_SET_VALUE Slutt01 > sluttposisjon
      RENAME_SET_VALUE Q > Mengde 1 vegkartlenke
      RENAME_SET_VALUE R > Mengde 2 vegkartlenke
      RENAME_SET_VALUE S > Mengde 1 url
      RENAME_SET_VALUE T > Mengde 2 url
    -> HTTPCaller
    -> ExpressionEvaluator
ExpressionEvaluator
    ACTION = Create New Attribute
    EXPRESSION = @Value(Mengde 2 startdato)-@Value(Mengde 1 sluttdato)
    VAL_ATTR = _mengde2_1_datocrash
    -> ExpressionEvaluator_2
ExpressionEvaluator_2
    ACTION = Create New Attribute
    EXPRESSION = @Value(Mengde 1 startdato)-@Value(Mengde 2 sluttdato)
    VAL_ATTR = _mengde1_2_datocrash
    -> Tester_5
Tester_5
    BOOL_OP = COMPOSITE
    COMPOSITE_TEST = 1 AND 2
    TEST_CLAUSE:
      NUM_TEST @Value(_mengde1_2_datocrash) < 0
      NUM_TEST @Value(_mengde2_1_datocrash) < 0
    TEST_MODE = NUM_TEST
    PASSED -> Tester_6
    FAILED -> Tester_5_Failed
Tester_6
    BOOL_OP = OR
    TEST_CLAUSE = TEST @Value(Mengde 1 startdato) = @Value(Mengde 2 startdato)
    TEST_MODE = TEST
    PASSED -> SubstringExtractor
    FAILED -> Tester_6_Failed
SubstringExtractor
    END = -1
    RESULT_ATTR = _substring
    SRC_STRING = @Value(Mengde 1 startdato)
    START = 4
    -> Tester_7
Tester_7
    BOOL_OP = OR
    TEST_CLAUSE = TEST @Value(_substring) = 0101
    TEST_MODE = TEST
    PASSED -> Nyttår
    FAILED -> samme_startdato
Nyttår: Inspector
samme_startdato: Inspector
Tester_6_Failed: Inspector
Tester_5_Failed: Inspector
HTTPCaller [off]
    CONNECTION_TIMEOUT_LENGTH = 60
    CUSTOM_HEADERS = Accept;application/json
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body1
    TARGET_ATTR_ENCODING = auto-detect
    TARGET_URL = @Value(Mengde 1 url)
    TRANSFER_TIMEOUT_LENGTH = 90
    USE_COOKIES = No
    VERIFY_SSL_CERTIFICATES = Yes
    -> JSONFragmenter
    <REJECTED> -> HTTPCaller__Rejected_
HTTPCaller__Rejected_: Logger
    LOG_FEATURE = LOG_ONLY
    MAXCOORDS = 20
    MAXFEATS = 20
    MESSAGE = Feature is:
    SEVERITY = INFO
    LOGGED -> HTTPCaller_2
JSONFragmenter
    EXPLODE_FORMAT = JSON
    EXTRACT_ATTR = Yes
    JSON_ATTR = _response_body1
    JSON_QUERY = json["egenskaper"][*]
    READ_FROM_FILE = NO
    RECURSIVE = Yes
    REJECT_EMPTY_LISTS = YES
    FRAGMENTS -> JSONFragmenter_2
JSONFragmenter_2
    EXPLODE_FORMAT = JSON
    EXTRACT_ATTR = Yes
    JSON_ATTR = _response_body1
    JSON_QUERY = json[*]
    NEW_ATTRIBUTES = navn verdi
    READ_FROM_FILE = NO
    RECURSIVE = Yes
    REJECT_EMPTY_LISTS = YES
    FRAGMENTS -> Tester
Tester
    BOOL_OP = AND
    TEST_CLAUSE:
      TEST @Value(navn) = ÅDT, total
      TEST @Value(json_index) = egenskapstype
    TEST_MODE = TEST
    PASSED -> AttributeRenamer_2
    FAILED -> Tester_2
AttributeRenamer_2
    ATTR_TABLE = RENAME_SET_DEFAULT verdi > Mengde 1 ÅDT
    MISSING_INPUT_ATTRS = REMOVE
    -> FeatureMerger [REQUESTOR]
Tester_2
    BOOL_OP = AND
    TEST_CLAUSE:
      TEST @Value(navn) = ÅDT, andel lange kjøretøy
      TEST @Value(json_index) = egenskapstype
    TEST_MODE = TEST
    PASSED -> AttributeRenamer
AttributeRenamer
    ATTR_TABLE = RENAME_SET_DEFAULT verdi > Mengde 1 Andel lange kjt
    MISSING_INPUT_ATTRS = REMOVE
    -> FeatureMerger [SUPPLIER]
FeatureMerger
    ATTR_ACCUM_MODE = Merge Supplier
    ATTR_CONFLICT_RES = Use Requestor
    IGNORE_NULLS = No
    JOIN_KEYS = @Value(xlsx_row_id) @Value(xlsx_row_id) AUTO
    MERGE_TYPE = Attributes Only
    PROCESS_DUPS = NO
    REJECT_NULL_MISSING_KEYS = No
    SUPPLIERS_FIRST = No
    MERGED -> Junction
    UNMERGED_REQUESTOR -> Junction
    UNUSED_SUPPLIER -> Junction
    <REJECTED> -> FeatureMerger__Rejected_
Junction
    -> HTTPCaller_2
HTTPCaller_2
    CONNECTION_TIMEOUT_LENGTH = 60
    CUSTOM_HEADERS = Accept;application/json
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body1
    TARGET_ATTR_ENCODING = auto-detect
    TARGET_URL = @Value(Mengde 2 url)
    TRANSFER_TIMEOUT_LENGTH = 90
    USE_COOKIES = No
    VERIFY_SSL_CERTIFICATES = Yes
    -> JSONFragmenter_3
    <REJECTED> -> Logger
Logger
    LOG_FEATURE = LOG_ONLY
    MAXCOORDS = 20
    MAXFEATS = 20
    MESSAGE = Feature is:
    SEVERITY = INFO
    LOGGED -> Ark1 (writer XLSXW_1)
JSONFragmenter_3
    EXPLODE_FORMAT = JSON
    EXTRACT_ATTR = Yes
    JSON_ATTR = _response_body1
    JSON_QUERY = json["egenskaper"][*]
    READ_FROM_FILE = NO
    RECURSIVE = Yes
    REJECT_EMPTY_LISTS = YES
    FRAGMENTS -> JSONFragmenter_4
JSONFragmenter_4
    EXPLODE_FORMAT = JSON
    EXTRACT_ATTR = Yes
    JSON_ATTR = _response_body1
    JSON_QUERY = json[*]
    NEW_ATTRIBUTES = navn verdi
    READ_FROM_FILE = NO
    RECURSIVE = Yes
    REJECT_EMPTY_LISTS = YES
    FRAGMENTS -> Tester_3
Tester_3
    BOOL_OP = AND
    TEST_CLAUSE:
      TEST @Value(navn) = ÅDT, total
      TEST @Value(json_index) = egenskapstype
    TEST_MODE = TEST
    PASSED -> AttributeRenamer_4
    FAILED -> Tester_4
AttributeRenamer_4
    ATTR_TABLE = RENAME_SET_DEFAULT verdi > Mengde 2 ÅDT
    MISSING_INPUT_ATTRS = REMOVE
    -> FeatureMerger_2 [REQUESTOR]
Tester_4
    BOOL_OP = AND
    TEST_CLAUSE:
      TEST @Value(navn) = ÅDT, andel lange kjøretøy
      TEST @Value(json_index) = egenskapstype
    TEST_MODE = TEST
    PASSED -> AttributeRenamer_3
AttributeRenamer_3
    ATTR_TABLE = RENAME_SET_DEFAULT verdi > Mengde 2 Andel lange kjt
    MISSING_INPUT_ATTRS = REMOVE
    -> FeatureMerger_2 [SUPPLIER]
FeatureMerger_2
    ATTR_ACCUM_MODE = Merge Supplier
    ATTR_CONFLICT_RES = Use Requestor
    IGNORE_NULLS = No
    JOIN_KEYS = @Value(xlsx_row_id) @Value(xlsx_row_id) AUTO
    MERGE_TYPE = Attributes Only
    PROCESS_DUPS = NO
    REJECT_NULL_MISSING_KEYS = No
    SUPPLIERS_FIRST = No
    MERGED -> Junction_2
    UNMERGED_REQUESTOR -> Junction_2
    UNUSED_SUPPLIER -> Junction_2
Junction_2
    -> AttributeManager_2
AttributeManager_2
    ATTR_TABLE:
      REMOVE xlsx_row_id
      REMOVE _response_body1
      REMOVE _http_status_code
      REMOVE json_type
      REMOVE json_index
      REMOVE navn
    -> FeatureMerger_2_Merged
    -> Ark1 (writer XLSXW_1)
Ark1 (writer XLSXW_1)
    attributes: Mengde 1 NVDB-ID number(20), Mengde 1 Versjon number(20), Mengde 1 ÅDT number(20), Mengde 1 Andel lange kjt number(20), Mengde 1 startdato string(20), Mengde 1 sluttdato string(20), År, gjelder for number(20), Mengde 2 NVDB-ID number(20), Mengde 2 versjon number(20), Mengde 2 startdato string(20), Mengde 2 sluttdato string(20), Mengde 2 ÅDT number(20), Mengde 2 Andel lange kjt string(20), VeglenkesekvensId number(20), startposisjon number(20), sluttposisjon number(20), Veg string(10), Strekning string(10), Sekvens number(10), Del string(10), Mengde 1 vegkartlenke string(71), Mengde 2 vegkartlenke string(71), Mengde 1 url string(68), Mengde 2 url string(68)
FeatureMerger_2_Merged: Inspector
FeatureMerger__Rejected_: Inspector
