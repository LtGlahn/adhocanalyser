FME workspace tynnFjelloverganger.fmw

Parameters:
- SourceDataset_OGCGEOPACKAGE = $(FME_MF_DIR)fjelloverganger.gpkg   # GeoPackage File
- DestDataset_OGCGEOPACKAGE = $(FME_MF_DIR)bearbeidedeFjelloverganger.gpkg   # GeoPackage File

Readers:
- OGCGEOPACKAGE_1: OGCGEOPACKAGE from $(SourceDataset_OGCGEOPACKAGE)

Writers:
- OGCGEOPACKAGE_2: OGCGEOPACKAGE to $(DestDataset_OGCGEOPACKAGE) in EPSG:25833

fjelloverganger (reader OGCGEOPACKAGE_1)
    attributes: objekttype int, nvdbId int, versjon int, startdato text, Stedlig beredskap text, Ekstra vintervedlikehold text, Fjellovergang text, Ansvarlig VTS text, Vinterstengt, til dato text, Snødybde double, Navn text, Vinterstengt, fra dato text, Sted, fra text, Antall stengte døgn double, Sted, til text, Sted lokalt, fra text, Sted lokalt, til text, relasjoner text, veglenkesekvensid int, detaljnivå text, typeVeg text, kommune int, fylke int, vref text, veglenkeType text, vegkategori text, fase text, vegnummer int, startposisjon double, sluttposisjon double,
      segmentlengde double, adskilte_lop text, trafikantgruppe text, geometri text, Tilleggsinformasjon text, Nattestengt, til dato text, Nattestengt, fra dato text, Avgrensa vinterdrift, fra dato text, Avgrensa vinterdrift, til dato text, fid int,PrimaryKey
    -> LineCombiner
LineCombiner
    ACCUM_ATTRS_NAME = Use Attributes From One Feature
    BREAK = no
    BREAK_CONNECTION_ATTRIBUTES = Navn
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> AttributeKeeper
AttributeKeeper
    CREATE_BULK_MODE_FEATURES = NO
    KEEP_ATTRS = fase,Navn,vegkategori,vegnummer
    -> GeometryFilter
    -> orginal_oppløsning (writer OGCGEOPACKAGE_2)
    -> Generalizer
    -> Generalizer_2
    -> Generalizer_3
    -> Generalizer_4
Generalizer_3
    ALG_TEXT = Douglas (Generalize)
    PRESERVE = No
    PRESERVE_PATHS = No
    TOLERANCE = 100
    -> redusert 100m toleranse (writer OGCGEOPACKAGE_2)
redusert 100m toleranse (writer OGCGEOPACKAGE_2)
    attributes: Navn text, vegkategori text, fase text, vegnummer int
Generalizer_2
    ALG_TEXT = Douglas (Generalize)
    PRESERVE = No
    PRESERVE_PATHS = No
    TOLERANCE = 50
    -> redusert 50m toleranse (writer OGCGEOPACKAGE_2)
redusert 50m toleranse (writer OGCGEOPACKAGE_2)
    attributes: Navn text, vegkategori text, fase text, vegnummer int
GeometryFilter
    FILTER_MODE = SIMPLE
    FILTER_MULTI = FILTER_TYPES]Curve]FME_CONTROLLER_QUERY_FILE]]FME_CONTROLLER_CHOICE]Simple
    <UNFILTERED> -> fjelloverganger
fjelloverganger: Inspector
Generalizer_4
    ALG_TEXT = Douglas (Generalize)
    PRESERVE = No
    PRESERVE_PATHS = No
    TOLERANCE = 10
    -> redusert 20m toleranse (writer OGCGEOPACKAGE_2)
redusert 20m toleranse (writer OGCGEOPACKAGE_2)
    attributes: Navn text, vegkategori text, fase text, vegnummer int
Generalizer
    ALG_TEXT = Douglas (Generalize)
    PRESERVE = No
    PRESERVE_PATHS = No
    TOLERANCE = 10
    -> redusert 10m toleranse (writer OGCGEOPACKAGE_2)
redusert 10m toleranse (writer OGCGEOPACKAGE_2)
    attributes: Navn text, vegkategori text, fase text, vegnummer int
orginal_oppløsning (writer OGCGEOPACKAGE_2)
    attributes: Navn text, vegkategori text, fase text, vegnummer int
