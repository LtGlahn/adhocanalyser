FME workspace fjelloverganger2polygon.fmw

Parameters:
- SourceDataset_OGCGEOPACKAGE = $(FME_MF_DIR)fjelloverganger.gpkg   # GeoPackage File

Readers:
- OGCGEOPACKAGE_1: OGCGEOPACKAGE from $(SourceDataset_OGCGEOPACKAGE)

fjelloverganger (reader OGCGEOPACKAGE_1)
    attributes: objekttype int, nvdbId int, versjon int, startdato text, Stedlig beredskap text, Ekstra vintervedlikehold text, Fjellovergang text, Ansvarlig VTS text, Vinterstengt, til dato text, Snødybde double, Navn text, Vinterstengt, fra dato text, Sted, fra text, Antall stengte døgn double, Sted, til text, Sted lokalt, fra text, Sted lokalt, til text, relasjoner text, veglenkesekvensid int, detaljnivå text, typeVeg text, kommune int, fylke int, vref text, veglenkeType text, vegkategori text, fase text, vegnummer int, startposisjon double, sluttposisjon double,
      segmentlengde double, adskilte_lop text, trafikantgruppe text, geometri text, Tilleggsinformasjon text, Nattestengt, til dato text, Nattestengt, fra dato text, Avgrensa vinterdrift, fra dato text, Avgrensa vinterdrift, til dato text, fid int,PrimaryKey
    -> Bufferer
Bufferer
    ANGLE = 22.5
    CAP_STYLE = Arc
    CORNER_STYLE = Arc
    MODE = AREA
    OFFSET = 200
    OFFSET_UNITS = NONE
    PRECISION = APPROX
    BUFFERED -> Dissolver
Dissolver
    ACCUM_INPUT_ATTRS = Use Attributes From One Feature
    CLEANING_TOLERANCE = Automatic
    CONNECT_Z_MODE = First Wins
    DEAGGREGATE_INPUT = Yes
    GROUP_BY = Navn
    AREA -> Generalizer_5
Generalizer_5
    ALG_TEXT = Douglas (Generalize)
    PRESERVE = No
    PRESERVE_PATHS = No
    TOLERANCE = 100
    -> Reprojector
Reprojector
    DEST = EPSG:4326
    INTERPOLATION_TYPE_NAME = Nearest Neighbor
    RASTER_CELL_SIZE = Preserve Cells
    RASTER_TOLERANCE = 0.0
    SOURCE = EPSG:25833
    REPROJECTED -> GeometryExtractor_2
GeometryExtractor_2
    ATTR = _geometry
    KIND_LONG = OGC Well Known Text
    OGCVERSION = 1.2
    OGC_WKT_PRECISION_DISPLAY = 32-bit
    REMOVE_GEOMETRY = No
    -> AttributeCreator
AttributeCreator
    ATTR_TABLE = SET_TO CQL-filter = CQL_FILTER=Within(geometry,@Value(_geometry) )+AND+properties.situationRecord.severity=none
    -> Generalizer_5_Output
Generalizer_5_Output: Inspector
